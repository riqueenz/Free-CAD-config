import FreeCAD
import Part
import PartDesignGui

planilhaProgramaCNC = App.activeDocument().getObject('Programa_CNC')
def lerLinha(x):
    Lado = planilhaProgramaCNC.get('B'+str(x))
    if x>3:
        ladoAnterior = planilhaProgramaCNC.get('B'+str(x-1))
    else:
        ladoAnterior = Lado
    T = planilhaProgramaCNC.get('D'+str(x))
    descFerr = planilhaProgramaCNC.get('E'+str(x))
    diam = planilhaProgramaCNC.get('F'+str(x))
    S = planilhaProgramaCNC.get('H'+str(x))
    F = planilhaProgramaCNC.get('J'+str(x))
    X = planilhaProgramaCNC.get('L'+str(x))
    Y = planilhaProgramaCNC.get('N'+str(x))
    Zi = planilhaProgramaCNC.get('P'+str(x))
    Zf = planilhaProgramaCNC.get('R'+str(x))
    sub = planilhaProgramaCNC.get('S'+str(x))
    L = planilhaProgramaCNC.get('T'+str(x))
    varX = planilhaProgramaCNC.get('U'+str(x))
    varY = planilhaProgramaCNC.get('V'+str(x))
    return Lado, T, descFerr, diam, S, F, X, Y, Zi, Zf, sub, L, varX, varY, ladoAnterior
    
#################################################################################################################3
sub = "INICIO DO BLOCO HIDRÁULICO"
linhaAtual = 3
linhaFolhaDeProcesso = 1

def transfEmVarTabela(var):
    var = var.replace("=P1","=Px1")
    var = var.replace("=P2","=Px2")
    var = var.replace("=P3","=Px3")
    var = var.replace("P1","Z_P1")
    var = var.replace("P2","X_P2")
    var = var.replace("P3","Y_P3")
    var = var.replace("Z_P101","Z_P101")
    var = var.replace("Z_P102","X_P102")
    var = var.replace("Z_P103","Y_P103")
    var = var.replace("=Px1","=P1")
    var = var.replace("=Px2","=P2")
    var = var.replace("=Px3","=P3")
    #print(var)
    return var

def testePreenchimento(linha):
    planilhaProgramaCNC = App.activeDocument().getObject('Programa_CNC')
    linha = str(linha)
    testeVarX = planilhaProgramaCNC.get('U'+linha)
    testeVarX = '=L'+str(linha)+'-(' + str(testeVarX) + ')'
    testeVarX = transfEmVarTabela(testeVarX)
    planilhaProgramaCNC.set('Y'+linha,str(testeVarX))
    print('varX = '+str(testeVarX))
    testeVarY = planilhaProgramaCNC.get('V'+linha)
    testeVarY = '=N'+str(linha)+'-(' + str(testeVarY) + ')'
    testeVarY = transfEmVarTabela(testeVarY)
    planilhaProgramaCNC.set('Z'+linha,str(testeVarY))
    print('varY = '+str(testeVarY))
    testeZi = planilhaProgramaCNC.get('W'+linha)
    testeZi = '=P'+str(linha)+'-(' + str(testeZi) + ')'
    testeZi = transfEmVarTabela(testeZi)
    planilhaProgramaCNC.set('AA'+linha,str(testeZi))
    print('varZi = '+str(testeZi))
    testeZf = planilhaProgramaCNC.get('X'+linha)
    testeZf = '=R'+str(linha)+'-(' + str(testeZf) + ')'
    testeZf = transfEmVarTabela(testeZf)
    print('varZi = '+str(testeZf))
    planilhaProgramaCNC.set('AB'+linha,str(testeZf))
    if int(linha) == 3:
        planilhaProgramaCNC.set('AA3','0')
    planilhaProgramaCNC.recompute()
    
while sub != "FIM DO BLOCO HIDRÁULICO":
    Lado, T, descFerr, diam, S, F, X, Y, Zi, Zf, sub, L, varX, varY, ladoAnterior = lerLinha(linhaAtual)
    print(sub)
    if sub == "INICIO DO BLOCO HIDRÁULICO":
        testePreenchimento(linhaAtual)
    elif sub == "TROCA DE FERRAMENTA":
        testePreenchimento(linhaAtual)
    elif sub == "APROXIMAR DO FURO":
        testePreenchimento(linhaAtual)
    elif sub == "LIGAR REFRIGERAÇÃO":
        testePreenchimento(linhaAtual)
    elif sub == "SAIR DO FURO":
        testePreenchimento(linhaAtual)
    elif sub == "DESLIGAR REFRIGERAÇÃO":
        testePreenchimento(linhaAtual)
    elif sub == "TROCAR LADO BLOCO HIDRAULICO":
        testePreenchimento(linhaAtual)
    elif sub == "PICA-PAU SEM RETORNO":
        testePreenchimento(linhaAtual)
    elif sub == "PICA-PAU COM RETORNO A Z2":
        testePreenchimento(linhaAtual)
    elif sub == "FURO DE CENTRO":
        testePreenchimento(linhaAtual)
        
        
sub = "INICIO DO BLOCO HIDRÁULICO"
linhaAtual = 3
linhaFolhaDeProcesso = 1
