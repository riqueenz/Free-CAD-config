# -*- coding: utf-8 -*-

# Macro Begin: /home/henrique/snap/freecad/common/part.FCMacro +++++++++++++++++++++++++++++++++++++++++++++++++
import FreeCAD
import Part
import PartDesignGui

App.newDocument()
#App.activeDocument().addObject( 'PartDesign::CoordinateSystem', 'Lado_1' )
#App.ActiveDocument.ActiveObject.Placement = App.Placement(App.Vector(0.00,0.00,P101_Lado_1_Z),App.Rotation(App.Vector(0.00,0.00,1.00),0.00))

pastaPlanilhas = App.activeDocument().addObject('App::DocumentObjectGroup','Planilhas')

planilhaSubProgramas = App.activeDocument().addObject('Spreadsheet::Sheet','Sub_programas')
pastaPlanilhas.addObject(planilhaSubProgramas)
planilhaSubProgramas.setColumnWidth('A',50)
planilhaSubProgramas.setColumnWidth('B',300)
planilhaSubProgramas.set('B1','INICIO DO BLOCO HIDRÁULICO')
planilhaSubProgramas.set('B2','TROCA DE FERRAMENTA')
planilhaSubProgramas.set('B3','APROXIMAR DO FURO')
planilhaSubProgramas.set('B4','LIGAR REFRIGERAÇÃO')
planilhaSubProgramas.set('B5','SAIR DO FURO')
planilhaSubProgramas.set('B6','DESLIGAR REFRIGERAÇÃO')
planilhaSubProgramas.set('A7','SUB 1')
planilhaSubProgramas.set('B7','VERIFICAR K NA TABELA DE FERRAMENTAS')
planilhaSubProgramas.set('A8','SUB 2')
planilhaSubProgramas.set('B8','TROCAR LADO BLOCO HIDRAULICO')
planilhaSubProgramas.set('A9','SUB 3')
planilhaSubProgramas.set('B9','PICA-PAU SEM RETORNO')
planilhaSubProgramas.set('A10','SUB 4')
planilhaSubProgramas.set('B10','PICA-PAU COM RETORNO A Z2')
planilhaSubProgramas.set('B11','FURO DE CENTRO')
planilhaSubProgramas.set('B12','CARTUCHO')
planilhaSubProgramas.set('B13','FIM DO BLOCO HIDRÁULICO')
planilhaSubProgramas.recompute()

planilhaFerramentas = App.activeDocument().addObject('Spreadsheet::Sheet','Ferramentas')
planilhaFerramentas.Label = "Ferramentas"
planilhaFerramentas.setAlignment('A1:F25', 'center', 'keep')
planilhaFerramentas.setAlignment('A1:F25', 'vcenter', 'keep')
planilhaFerramentas.setBackground('A1:F1', (0.752941,0.752941,0.752941,1.000000))
planilhaFerramentas.set('A1', 'T')
planilhaFerramentas.set('B1', 'Ferramenta')
planilhaFerramentas.set('C1', 'Diam')
planilhaFerramentas.mergeCells('D1:E1')
planilhaFerramentas.set('D1', 'S')
planilhaFerramentas.mergeCells('F1:G1')
planilhaFerramentas.set('F1', 'F')
planilhaFerramentas.setColumnWidth('A',30)
planilhaFerramentas.setColumnWidth('B',150)
planilhaFerramentas.setColumnWidth('C',50)
planilhaFerramentas.setColumnWidth('D',30)
planilhaFerramentas.setColumnWidth('E',40)
planilhaFerramentas.setColumnWidth('F',30)
planilhaFerramentas.setColumnWidth('G',30)
planilhaFerramentas.set('D2:D25','S')
planilhaFerramentas.set('F2:F25','F')
x = 1
while x<25:
    planilhaFerramentas.set('A'+str(x+1), str(x))
    x += 1
linha = 1
planilhaFerramentas.set('B'+str(linha+1),'BROCA CENTRO')
planilhaFerramentas.set('C'+str(linha+1),'5')
planilhaFerramentas.set('E'+str(linha+1),'1000')
planilhaFerramentas.set('G'+str(linha+1),'50')
linha = 2
planilhaFerramentas.set('B'+str(linha+1),'BROCA ACO RAPIDO')
planilhaFerramentas.set('C'+str(linha+1),'15,5')
planilhaFerramentas.set('E'+str(linha+1),'350')
planilhaFerramentas.set('G'+str(linha+1),'25')
linha = 3
planilhaFerramentas.set('B'+str(linha+1),'BROCA ACO RAPIDO')
planilhaFerramentas.set('C'+str(linha+1),'20')
planilhaFerramentas.set('E'+str(linha+1),'350')
planilhaFerramentas.set('G'+str(linha+1),'25')
linha = 4
planilhaFerramentas.set('B'+str(linha+1),'ALARGADOR')
planilhaFerramentas.set('C'+str(linha+1),'16')
planilhaFerramentas.set('E'+str(linha+1),'120')
planilhaFerramentas.set('G'+str(linha+1),'10')
linha = 5
planilhaFerramentas.set('B'+str(linha+1),'BROCA ESCAREAR 37 GRAUS')
planilhaFerramentas.set('C'+str(linha+1),'30')
planilhaFerramentas.set('E'+str(linha+1),'120')
planilhaFerramentas.set('G'+str(linha+1),'10')
linha = 6
planilhaFerramentas.set('B'+str(linha+1),'MACHO 7/8 UNF 14 FIOS/POL')
planilhaFerramentas.set('C'+str(linha+1),'22')
planilhaFerramentas.set('E'+str(linha+1),'120')
planilhaFerramentas.set('G'+str(linha+1),'10')
linha = 11
planilhaFerramentas.set('B'+str(linha+1),'BROCA ACO RAPIDO')
planilhaFerramentas.set('C'+str(linha+1),'5')
planilhaFerramentas.set('E'+str(linha+1),'800')
planilhaFerramentas.set('G'+str(linha+1),'30')
linha = 12
planilhaFerramentas.set('B'+str(linha+1),'BROCA ACO RAPIDO')
planilhaFerramentas.set('C'+str(linha+1),'8,5')
planilhaFerramentas.set('E'+str(linha+1),'750')
planilhaFerramentas.set('G'+str(linha+1),'35')
linha = 13
planilhaFerramentas.set('B'+str(linha+1),'BROCA ACO RAPIDO')
planilhaFerramentas.set('C'+str(linha+1),'24')
planilhaFerramentas.set('E'+str(linha+1),'320')
planilhaFerramentas.set('G'+str(linha+1),'20')
linha = 14
planilhaFerramentas.set('B'+str(linha+1),'BROCA ACO RAPIDO')
planilhaFerramentas.set('C'+str(linha+1),'11,5')
planilhaFerramentas.set('E'+str(linha+1),'630')
planilhaFerramentas.set('G'+str(linha+1),'30')
linha = 15
planilhaFerramentas.set('B'+str(linha+1),'BROCA METAL DURO')
planilhaFerramentas.set('C'+str(linha+1),'4,2')
planilhaFerramentas.set('E'+str(linha+1),'2000')
planilhaFerramentas.set('G'+str(linha+1),'120')
linha = 16
planilhaFerramentas.set('B'+str(linha+1),'BROCA METAL DURO')
planilhaFerramentas.set('C'+str(linha+1),'5')
planilhaFerramentas.set('E'+str(linha+1),'2000')
planilhaFerramentas.set('G'+str(linha+1),'120')
linha = 17
planilhaFerramentas.set('B'+str(linha+1),'BROCA METAL DURO')
planilhaFerramentas.set('C'+str(linha+1),'6,5')
planilhaFerramentas.set('E'+str(linha+1),'2000')
planilhaFerramentas.set('G'+str(linha+1),'120')
linha = 18
planilhaFerramentas.set('B'+str(linha+1),'BROCA METAL DURO')
planilhaFerramentas.set('C'+str(linha+1),'6,8')
planilhaFerramentas.set('E'+str(linha+1),'2000')
planilhaFerramentas.set('G'+str(linha+1),'120')
linha = 19
planilhaFerramentas.set('B'+str(linha+1),'BROCA ACO RAPIDO')
planilhaFerramentas.set('C'+str(linha+1),'6,5')
planilhaFerramentas.set('E'+str(linha+1),'700')
planilhaFerramentas.set('G'+str(linha+1),'30')
linha = 20
planilhaFerramentas.set('B'+str(linha+1),'BROCA METAL DURO')
planilhaFerramentas.set('C'+str(linha+1),'8,5')
planilhaFerramentas.set('E'+str(linha+1),'1750')
planilhaFerramentas.set('G'+str(linha+1),'120')
linha = 21
planilhaFerramentas.set('B'+str(linha+1),'BROCA METAL DURO')
planilhaFerramentas.set('C'+str(linha+1),'11,5')
planilhaFerramentas.set('E'+str(linha+1),'1500')
planilhaFerramentas.set('G'+str(linha+1),'120')
linha = 22
planilhaFerramentas.set('B'+str(linha+1),'BROCA METAL DURO')
planilhaFerramentas.set('C'+str(linha+1),'14,5')
planilhaFerramentas.set('E'+str(linha+1),'1500')
planilhaFerramentas.set('G'+str(linha+1),'120')
linha = 23
planilhaFerramentas.set('B'+str(linha+1),'BROCA ACO RAPIDO')
planilhaFerramentas.set('C'+str(linha+1),'18,5')
planilhaFerramentas.set('E'+str(linha+1),'400')
planilhaFerramentas.set('G'+str(linha+1),'25')
linha = 24
planilhaFerramentas.set('B'+str(linha+1),'BROCA ACO RAPIDO')
planilhaFerramentas.set('C'+str(linha+1),'10')
planilhaFerramentas.set('E'+str(linha+1),'660')
planilhaFerramentas.set('G'+str(linha+1),'30')
planilhaFerramentas.recompute()
pastaPlanilhas.addObject(planilhaFerramentas)

planilhaProgramaCNC = App.activeDocument().addObject('Spreadsheet::Sheet','Programa_CNC')
planilhaProgramaCNC.Label = "Programa CNC"
pastaPlanilhas.addObject(planilhaProgramaCNC)
planilhaProgramaCNC.setColumnWidth('A',50)
planilhaProgramaCNC.setColumnWidth('B',30)
planilhaProgramaCNC.setColumnWidth('C',30)
planilhaProgramaCNC.setColumnWidth('D',30)
planilhaProgramaCNC.setColumnWidth('E',200)
planilhaProgramaCNC.setColumnWidth('F',50)
planilhaProgramaCNC.setColumnWidth('G',30)
planilhaProgramaCNC.setColumnWidth('H',40)
planilhaProgramaCNC.setColumnWidth('I',30)
planilhaProgramaCNC.setColumnWidth('J',40)
planilhaProgramaCNC.setColumnWidth('K',30)
planilhaProgramaCNC.setColumnWidth('L',40)
planilhaProgramaCNC.setColumnWidth('M',30)
planilhaProgramaCNC.setColumnWidth('N',40)
planilhaProgramaCNC.setColumnWidth('O',30)
planilhaProgramaCNC.setColumnWidth('P',40)
planilhaProgramaCNC.setColumnWidth('Q',30)
planilhaProgramaCNC.setColumnWidth('R',40)
planilhaProgramaCNC.setColumnWidth('S',200)
planilhaProgramaCNC.setColumnWidth('T',30)
planilhaProgramaCNC.setAlignment('A1:X100', 'center', 'keep')
planilhaProgramaCNC.setAlignment('A1:X100', 'vcenter', 'keep')
planilhaProgramaCNC.setBackground('A2:X2', (0.752941,0.752941,0.752941,1.000000))
planilhaProgramaCNC.setAlignment('A3:A30', 'right', 'keep')
planilhaProgramaCNC.setAlignment('C3:C30', 'right', 'keep')
planilhaProgramaCNC.setAlignment('D3:D30', 'left', 'keep')
planilhaProgramaCNC.mergeCells('A1:D1')
planilhaProgramaCNC.setAlias('A1', 'numPrograma')
planilhaProgramaCNC.set('numPrograma', '1000')
planilhaProgramaCNC.setAlias('E1', 'nomePrograma')
planilhaProgramaCNC.set('nomePrograma', 'Nome do programa')
planilhaProgramaCNC.mergeCells('A2:B2')
planilhaProgramaCNC.mergeCells('C2:D2')
planilhaProgramaCNC.mergeCells('G1:H1')
planilhaProgramaCNC.mergeCells('G2:H2')
planilhaProgramaCNC.mergeCells('I1:J1')
planilhaProgramaCNC.setDisplayUnit('I1:J1', 'mm')
planilhaProgramaCNC.setDisplayUnit('U1:W1', 'mm')
planilhaProgramaCNC.setAlias('I1', 'Z_P101')
planilhaProgramaCNC.setAlias('U1', 'Z_P1')
planilhaProgramaCNC.setAlias('V1', 'X_P2')
planilhaProgramaCNC.setAlias('W1', 'Y_P3')
planilhaProgramaCNC.recompute()
planilhaProgramaCNC.set('Z_P1', '=Z_P101/2')
planilhaProgramaCNC.set('X_P2', '=X_P102/2')
planilhaProgramaCNC.set('Y_P3', '=Y_P103/2')
planilhaProgramaCNC.mergeCells('I2:J2')
planilhaProgramaCNC.mergeCells('K1:L1')
planilhaProgramaCNC.setDisplayUnit('M1:N1', 'mm')
planilhaProgramaCNC.setAlias('M1', 'X_P102')
planilhaProgramaCNC.mergeCells('K2:L2')
planilhaProgramaCNC.mergeCells('M1:N1')
planilhaProgramaCNC.mergeCells('M2:N2')
planilhaProgramaCNC.mergeCells('O1:P1')
planilhaProgramaCNC.mergeCells('O2:P2')
planilhaProgramaCNC.mergeCells('Q1:R1')
planilhaProgramaCNC.setDisplayUnit('Q1:R1', 'mm')
planilhaProgramaCNC.setAlias('Q1', 'Y_P103')
planilhaProgramaCNC.mergeCells('Q2:R2')
planilhaProgramaCNC.set('A2:A30','Lado')
planilhaProgramaCNC.set('C3:C30','- T')
planilhaProgramaCNC.set('G3:G30','S')
planilhaProgramaCNC.set('I3:I30','F')
planilhaProgramaCNC.set('K3:K30','X+')
planilhaProgramaCNC.set('M3:M30','Y')
planilhaProgramaCNC.set('O3:O30','Zi')
planilhaProgramaCNC.set('Q3:Q30','Zf')
planilhaProgramaCNC.set('C2','T')
planilhaProgramaCNC.set('E2','Descrição Ferramenta')
planilhaProgramaCNC.set('F2','Diam')
planilhaProgramaCNC.set('G2','S')
planilhaProgramaCNC.set('I2','F')
planilhaProgramaCNC.set('K2','X')
planilhaProgramaCNC.set('M2','Y')
planilhaProgramaCNC.set('O2','Zi')
planilhaProgramaCNC.set('Q2','Zf')
planilhaProgramaCNC.set('S2','Sub-programa')
planilhaProgramaCNC.set('T2','L')
planilhaProgramaCNC.set('U2','Var X')
planilhaProgramaCNC.set('V2','Var Y')
planilhaProgramaCNC.set('W2','Var Zi')
planilhaProgramaCNC.set('X2','Var Zf')
planilhaProgramaCNC.set('G1','Z P101 =')
planilhaProgramaCNC.set('K1','X P102 =')
planilhaProgramaCNC.set('O1','Y P103 =')
#Preencher tabela
planilhaProgramaCNC.set('I1','101,00')
planilhaProgramaCNC.set('M1','102,00')
planilhaProgramaCNC.set('Q1','103,00')
planilhaProgramaCNC.set('S3','INICIO DO BLOCO HIDRÁULICO')
planilhaProgramaCNC.set('S4','APROXIMAR DO FURO')
planilhaProgramaCNC.set('S5','LIGAR REFRIGERAÇÃO')
planilhaProgramaCNC.set('S6','FURO DE CENTRO')
planilhaProgramaCNC.set('S7','PICA-PAU SEM RETORNO')
planilhaProgramaCNC.set('S8','DESLIGAR REFRIGERAÇÃO')
planilhaProgramaCNC.set('S9','SAIR DO FURO')
planilhaProgramaCNC.set('S10','TROCAR LADO BLOCO HIDRAULICO')
planilhaProgramaCNC.set('S11','FIM DO BLOCO HIDRÁULICO')
planilhaProgramaCNC.set('B3','5')
planilhaProgramaCNC.set('D3','24')
planilhaProgramaCNC.set('E3','BROCA ACO RAPIDO')
planilhaProgramaCNC.set('F3','10')
planilhaProgramaCNC.set('H3','700')
planilhaProgramaCNC.set('J3','30')
planilhaProgramaCNC.set('L3','=Y_P103 - 40.75')
planilhaProgramaCNC.set('N3','=14 - Z_P101')
planilhaProgramaCNC.set('P3','100')
planilhaProgramaCNC.set('R3','100')
planilhaProgramaCNC.set('T3','P')
planilhaProgramaCNC.set('U3','P103-40.75')
planilhaProgramaCNC.set('V3','14-P101')
planilhaProgramaCNC.set('W3','100')
planilhaProgramaCNC.set('X3','100')
linha = 4
while linha<12:
    planilhaProgramaCNC.set('B'+str(linha),'=B'+str(linha-1))
    planilhaProgramaCNC.set('D'+str(linha),'=D'+str(linha-1))
    planilhaProgramaCNC.set('E'+str(linha),'=E'+str(linha-1))
    planilhaProgramaCNC.set('F'+str(linha),'=F'+str(linha-1))
    planilhaProgramaCNC.set('H'+str(linha),'=H'+str(linha-1))
    planilhaProgramaCNC.set('J'+str(linha),'=J'+str(linha-1))
    planilhaProgramaCNC.set('L'+str(linha),'=L'+str(linha-1))
    planilhaProgramaCNC.set('N'+str(linha),'=N'+str(linha-1))
    planilhaProgramaCNC.set('P'+str(linha),'=P'+str(linha-1))
    planilhaProgramaCNC.set('R'+str(linha),'=R'+str(linha-1))
    planilhaProgramaCNC.set('T'+str(linha),'=T'+str(linha-1))
    planilhaProgramaCNC.set('U'+str(linha),'=U'+str(linha-1))
    planilhaProgramaCNC.set('V'+str(linha),'=V'+str(linha-1))
    planilhaProgramaCNC.set('W'+str(linha),'=P'+str(linha))
    planilhaProgramaCNC.set('X'+str(linha),'=R'+str(linha))
    linha = linha + 1
linha = 6
planilhaProgramaCNC.set('D'+str(linha),'1')
planilhaProgramaCNC.set('E'+str(linha),'BROCA DE CENTRO')
planilhaProgramaCNC.set('F'+str(linha),'5')
planilhaProgramaCNC.set('H'+str(linha),'1000')
planilhaProgramaCNC.set('J'+str(linha),'50')
planilhaProgramaCNC.set('P'+str(linha),'0')
planilhaProgramaCNC.set('R'+str(linha),'-5')
linha = 7
planilhaProgramaCNC.set('D'+str(linha),'=D'+str(linha-2))
planilhaProgramaCNC.set('E'+str(linha),'=E'+str(linha-2))
planilhaProgramaCNC.set('F'+str(linha),'=F'+str(linha-2))
planilhaProgramaCNC.set('H'+str(linha),'=H'+str(linha-2))
planilhaProgramaCNC.set('J'+str(linha),'=J'+str(linha-2))
planilhaProgramaCNC.set('L'+str(linha),'=L'+str(linha-2))
planilhaProgramaCNC.set('N'+str(linha),'=N'+str(linha-2))
planilhaProgramaCNC.set('P'+str(linha),'0')
planilhaProgramaCNC.set('R'+str(linha),'-32')
planilhaProgramaCNC.set('T'+str(linha),'=T'+str(linha-2))
planilhaProgramaCNC.set('U'+str(linha),'=U'+str(linha-2))
planilhaProgramaCNC.set('V'+str(linha),'=V'+str(linha-2))
planilhaProgramaCNC.set('R4','2')
planilhaProgramaCNC.set('P5','2')
planilhaProgramaCNC.set('R9','100')
planilhaProgramaCNC.set('P9','100')
planilhaProgramaCNC.set('R10','100')
planilhaProgramaCNC.setBackground('A3:X3', (0.000000,1.000000,0.000000,1.000000))
planilhaProgramaCNC.setBackground('A9:X9', (1.000000,1.000000,0.000000,1.000000))
planilhaProgramaCNC.setBackground('A10:X10', (0.000000,1.000000,1.000000,1.000000))
planilhaProgramaCNC.setBackground('A11:X11', (1.000000,0.000000,0.000000,1.000000))
planilhaProgramaCNC.recompute()

#App.ActiveDocument.getObject('Sub_programas').ViewObject.doubleClicked()
#App.ActiveDocument.getObject('Ferramentas').ViewObject.doubleClicked()
App.ActiveDocument.getObject('Programa_CNC').ViewObject.doubleClicked()
App.activeDocument().recompute(None,True,True)
