# -*- coding: utf-8 -*-
import FreeCAD

def setParameter(group, parameter, value):
    if type(value) is int:
        if value > 255:
            group.SetUnsigned(parameter, value)
        else:
            group.SetInt(parameter, value)
    elif type(value) is float:
        group.SetFloat(parameter, value)
    elif type(value) is bool:
        group.SetBool(parameter, value)
    elif type(value) is str: 
        group.SetString(parameter, value)

dictionary = {
    FreeCAD.ParamGet('User parameter:BaseApp/Preferences/View'):
    {
        "BacklightColor" : 4294967295,
        "BackgroundColor" : 336897023,
        "BackgroundColor2" : 3857049087,
        "BackgroundColor3" : 3469659903,
        "BackgroundColor4" : 1869583359,
        "HighlightColor" : 3789624575,
        "SelectionColor" : 481107199,
        "DefaultShapeColor" : 3435973887,
        "DefaultShapeLineColor" : 421075455,
        "DefaultShapeVertexColor" : 421075455,
        "BoundingBoxColor" : 4294967295,
        "AnnotationTextColor" : 3402287871,
        "SketchEdgeColor" : 4294967295,
        "SketchVertexColor" : 4294967295,
        "EditedEdgeColor" : 5636095,
        "EditedVertexColor" : 5636095,
        "ConstructionColor" : 4294902015,
        "ExternalColor" : 1442775295,
        "InvalidSketchColor" : 4278190335,
        "FullyConstrainedColor" : 1044266751,
        "InternalAlignedGeoColor" : 5636095,
        "FullyConstraintElementColor" : 1044266751,
        "FullyConstraintConstructionElementColor" : 2868871167,
        "FullyConstraintInternalAlignmentColor" : 1044266751,
        "FullyConstraintConstructionPointColor" : 1044266751,
        "ConstrainedIcoColor" : 4283760895,
        "NonDrivingConstrDimColor" : 2555903,
        "ConstrainedDimColor" : 4280680703,
        "ExprBasedConstrDimColor" : 4286523135,
        "DeactivatedConstrDimColor" : 2139062271,
        "CursorTextColor" : 5636095,
        "CursorCrosshairColor" : 4294967295,
        "CreateLineColor" : 5636095,
        "AntiAliasing" : 4,
        "UseVBO" : True,

    },
    FreeCAD.ParamGet('User parameter:BaseApp/Preferences/Mod/Part') : {"MeshDeviation" : 0.2},
    FreeCAD.ParamGet('User parameter:BaseApp/Preferences/Mod/Mesh') : {"MaxDeviationExport" : 0.02},
    FreeCAD.ParamGet('User parameter:BaseApp/Preferences/DockWindows/TreeView') : {"Enabled" : True},
    FreeCAD.ParamGet('User parameter:BaseApp/Preferences/DockWindows/PropertyView') : {"Enabled" : False},
    FreeCAD.ParamGet('User parameter:BaseApp/Preferences/DockWindows/DAGView') : {"Enabled" : False},
    FreeCAD.ParamGet('User parameter:BaseApp/Preferences/DockWindows/ComboView') : {"Enabled" : False},
    FreeCAD.ParamGet('User parameter:BaseApp/MainWindow/DockWindows') :
    {
        "Std_ReportView" : False,
        "Std_SelectionView" : False,
        "Std_ComboView" : True,
        "Std_PythonView" : False,
        "Std_TreeView" : True,
        "Std_PropertyView" : False,
        "Std_ReportView" : False
    },
    FreeCAD.ParamGet('User parameter:BaseApp/MainWindow/Toolbars') :
    {
        "File" : True,
        "Workbench" : False,
        "Macro" : False,
        "View" : True,
        "Structure" : True,
        "Navigation" : False,
        "Part Design Modeling" : True,
        "Part Design Helper" : True,
        "Sketcher" : True,
        "Sketcher geometries" : True,
        "Sketcher constraints" : True,
        "Sketcher tools" : False,
        "Sketcher B-spline tools" : False,
        "Mesure" : True,
        "Tabs" : True,
        "Sketcher virtual space" : False
    },
    FreeCAD.ParamGet('User parameter:BaseApp/TabBar') :
    {
        "Enabled" : "MoocWorkbench,SketcherWorkbench,PartDesignWorkbench,TechDrawWorkbench,A2plusWorkbench,SpreadsheetWorkbench,SMWorkbench,SurfaceWorkbench",
        "Orientation" : "South",
        "Partially" : "ArchWorkbench,DraftWorkbench,FemWorkbench,ImageWorkbench,InspectionWorkbench,MeshWorkbench,NoneWorkbench,OpenSCADWorkbench,PartWorkbench,PathWorkbench,PointsWorkbench,RaytracingWorkbench,ReverseEngineeringWorkbench,RobotWorkbench,StartWorkbench,TestWorkbench,WebWorkbench",
        "Position" : "MoocWorkbench,SketcherWorkbench,PartDesignWorkbench,TechDrawWorkbench,A2plusWorkbench,SpreadsheetWorkbench,SMWorkbench,SurfaceWorkbench,ArchWorkbench,DraftWorkbench,FemWorkbench,ImageWorkbench,InspectionWorkbench,MeshWorkbench,NoneWorkbench,OpenSCADWorkbench,PartWorkbench,PathWorkbench,PointsWorkbench,RaytracingWorkbench,ReverseEngineeringWorkbench,RobotWorkbench,StartWorkbench,TestWorkbench,WebWorkbench",
        "PrefButton" : "On",
        "Style" : "IconText"
    },
    FreeCAD.ParamGet('User parameter:BaseApp/Preferences/MainWindow') : {"StyleSheet" : "Light-blue.qss"},
    FreeCAD.ParamGet('User parameter:BaseApp/Preferences/General') :
    {
        "AutoloadModule" : "PartDesignWorkbench",
    }
}
#A2Plus
param = FreeCAD.ParamGet('User parameter:Tux/PersistentToolbars/User/A2plusWorkbench')
param.SetString("Top", "Tabs,Break,File,Structure,Macro,View,Break,A2p_Part,A2p_Constraint,A2p_Misc,A2Diagnostics,A2p_Solver,Break,A2p_View")
param.SetString("Left", "")
param.SetString("Right", "")
param.SetString("Bottom", "Workbench")
param.SetBool("Saved", True)
#MOOC
param = FreeCAD.ParamGet('User parameter:Tux/PersistentToolbars/User/MoocWorkbench')
param.SetString("Top", "Tabs,Break,File,Structure,View,Macro,Break,MOOC")
param.SetString("Left", "")
param.SetString("Right", "")
param.SetString("Bottom", "Workbench")
param.SetBool("Saved", True)
#PartDesign
param = FreeCAD.ParamGet('User parameter:Tux/PersistentToolbars/User/PartDesignWorkbench')
param.SetString("Top", "Break,Tabs,Break,File,Structure,View,Break,Part Design Helper,Part Design Modeling,Measure")
param.SetString("Left", "")
param.SetString("Right", "")
param.SetString("Bottom", "Workbench")
param.SetBool("Saved", True)
#Sketcher
param = FreeCAD.ParamGet('User parameter:Tux/PersistentToolbars/User/SketcherWorkbench')
param.SetString("Top", "Tabs,Break,File,Structure,View,Macro,Break,Sketcher,Sketcher geometries,Sketcher constraints")
param.SetString("Left", "")
param.SetString("Right", "")
param.SetString("Bottom", "Workbench")
param.SetBool("Saved", True)
#SheetMetal
param = FreeCAD.ParamGet('User parameter:Tux/PersistentToolbars/User/SMWorkbench')
param.SetString("Top", "Tabs,Break,File,View,Macro,Structure,Break,Sheet Metal")
param.SetString("Left", "")
param.SetString("Right", "")
param.SetString("Bottom", "Workbench")
param.SetBool("Saved", True)
#Spreadsheet
param = FreeCAD.ParamGet('User parameter:Tux/PersistentToolbars/User/SpreadsheetWorkbench')
param.SetString("Top", "Tabs,Break,File,View,Macro,Structure,Break,Spreadsheet")
param.SetString("Left", "")
param.SetString("Right", "")
param.SetString("Bottom", "Workbench")
param.SetBool("Saved", True)
#Surface
param = FreeCAD.ParamGet('User parameter:Tux/PersistentToolbars/User/SurfaceWorkbench')
param.SetString("Top", "Tabs,Break,File,View,Macro,Structure,Break,Surface")
param.SetString("Left", "")
param.SetString("Right", "")
param.SetString("Bottom", "Workbench")
param.SetBool("Saved", True)
#TechDraw
param = FreeCAD.ParamGet('User parameter:Tux/PersistentToolbars/User/TechDrawWorkbench')
param.SetString("Top", "Break,Tabs,Break,File,Structure,View,Break,TechDraw Dimensions,TechDraw File Access,TechDraw Decoration,TechDraw Pages,TechDraw Annotation,TechDraw Stacking,TechDraw Views,TechDraw Clips,TechDraw Attributes,TechDraw Centerlines,TechDraw Extend Dimensions")
param.SetString("Left", "")
param.SetString("Right", "")
param.SetString("Bottom", "Workbench")
param.SetBool("Saved", True)
#Fasteners
param = FreeCAD.ParamGet('User parameter:BaseApp/Preferences/Mod/Fasteners')
param.SetInt("ScrewToolbarGroupMode", 2)
for group, items in dictionary.items():
    for key in items:
        setParameter(group, key, items[key])
#Disable some toolbars
param = FreeCAD.ParamGet('User parameter:BaseApp/MainWindow/Toolbars')
param.SetBool("File", True)
param.SetBool("Workbench", False)
param.SetBool("Macro", False)
param.SetBool("View", True)
param.SetBool("Navigation", False)
param.SetBool("Structure", True)
#Report view
param = FreeCAD.ParamGet('User parameter:BaseApp/Preferences/OutputWindow')
param.SetBool("checkShowReportViewOnError", False)
param.SetBool("checkShowReportViewOnLogMessage", False)
param.SetBool("checkShowReportViewOnNormalMessage", False)
param.SetBool("checkShowReportViewOnWarning", False)
