# -*- coding: utf-8 -*-

# Macro Begin: /home/henrique/snap/freecad/common/criarBloco.FCMacro +++++++++++++++++++++++++++++++++++++++++++++++++
import FreeCAD
import PartDesignGui
import Part

# Gui.runCommand('Std_DlgMacroRecord',0)
Gui.activateWorkbench("PartWorkbench")
### Begin command Part_Box
App.ActiveDocument.addObject("Part::Box","Box")
App.ActiveDocument.ActiveObject.Label = "Cube"
# Object created at document root.
App.ActiveDocument.recompute()
# Gui.SendMsgToActiveView("ViewFit")
### End command Part_Box
# Gui.Selection.addSelection('Unnamed','Box')
FreeCAD.getDocument('Unnamed').getObject('Box').Length = '1.00 mm'

FreeCAD.getDocument('Unnamed').getObject('Box').Length = '10.00 mm'

FreeCAD.getDocument('Unnamed').getObject('Box').Length = '100.00 mm'

FreeCAD.getDocument('Unnamed').getObject('Box').Width = '1.00 mm'

FreeCAD.getDocument('Unnamed').getObject('Box').Width = '10.00 mm'

FreeCAD.getDocument('Unnamed').getObject('Box').Width = '100.00 mm'

FreeCAD.getDocument('Unnamed').getObject('Box').Height = '5.00 mm'

FreeCAD.getDocument('Unnamed').getObject('Box').Height = '50.00 mm'

# Gui.Selection.clearSelection()
### Begin command Part_Cylinder
App.ActiveDocument.addObject("Part::Cylinder","Cylinder")
App.ActiveDocument.ActiveObject.Label = "Cylinder"
# Object created at document root.
App.ActiveDocument.recompute()
# Gui.SendMsgToActiveView("ViewFit")
### End command Part_Cylinder
# Gui.Selection.addSelection('Unnamed','Cylinder')
FreeCAD.getDocument('Unnamed').getObject('Cylinder').Placement = App.Placement(App.Vector(0.00,0.00,-1.00),App.Rotation(App.Vector(0.00,0.00,1.00),0.00))

FreeCAD.getDocument('Unnamed').getObject('Cylinder').Placement = App.Placement(App.Vector(0.00,0.00,-2.00),App.Rotation(App.Vector(0.00,0.00,1.00),0.00))

FreeCAD.getDocument('Unnamed').getObject('Cylinder').Placement = App.Placement(App.Vector(0.00,0.00,-3.00),App.Rotation(App.Vector(0.00,0.00,1.00),0.00))

FreeCAD.getDocument('Unnamed').getObject('Cylinder').Placement = App.Placement(App.Vector(0.00,0.00,-4.00),App.Rotation(App.Vector(0.00,0.00,1.00),0.00))

FreeCAD.getDocument('Unnamed').getObject('Cylinder').Placement = App.Placement(App.Vector(0.00,0.00,-3.00),App.Rotation(App.Vector(0.00,0.00,1.00),0.00))

FreeCAD.getDocument('Unnamed').getObject('Cylinder').Placement = App.Placement(App.Vector(0.00,0.00,-2.00),App.Rotation(App.Vector(0.00,0.00,1.00),0.00))

FreeCAD.getDocument('Unnamed').getObject('Cylinder').Placement = App.Placement(App.Vector(0.00,0.00,-1.00),App.Rotation(App.Vector(0.00,0.00,1.00),0.00))

FreeCAD.getDocument('Unnamed').getObject('Cylinder').Placement = App.Placement(App.Vector(0.00,0.00,0.00),App.Rotation(App.Vector(0.00,0.00,1.00),0.00))

FreeCAD.getDocument('Unnamed').getObject('Cylinder').Placement = App.Placement(App.Vector(0.00,0.00,1.00),App.Rotation(App.Vector(0.00,0.00,1.00),0.00))

FreeCAD.getDocument('Unnamed').getObject('Cylinder').Placement = App.Placement(App.Vector(0.00,0.00,2.00),App.Rotation(App.Vector(0.00,0.00,1.00),0.00))

FreeCAD.getDocument('Unnamed').getObject('Cylinder').Placement = App.Placement(App.Vector(0.00,0.00,3.00),App.Rotation(App.Vector(0.00,0.00,1.00),0.00))

FreeCAD.getDocument('Unnamed').getObject('Cylinder').Placement = App.Placement(App.Vector(0.00,0.00,5.00),App.Rotation(App.Vector(0.00,0.00,1.00),0.00))

FreeCAD.getDocument('Unnamed').getObject('Cylinder').Placement = App.Placement(App.Vector(0.00,0.00,6.00),App.Rotation(App.Vector(0.00,0.00,1.00),0.00))

FreeCAD.getDocument('Unnamed').getObject('Cylinder').Placement = App.Placement(App.Vector(0.00,0.00,7.00),App.Rotation(App.Vector(0.00,0.00,1.00),0.00))

FreeCAD.getDocument('Unnamed').getObject('Cylinder').Placement = App.Placement(App.Vector(0.00,0.00,8.00),App.Rotation(App.Vector(0.00,0.00,1.00),0.00))

FreeCAD.getDocument('Unnamed').getObject('Cylinder').Placement = App.Placement(App.Vector(0.00,0.00,9.00),App.Rotation(App.Vector(0.00,0.00,1.00),0.00))

FreeCAD.getDocument('Unnamed').getObject('Cylinder').Placement = App.Placement(App.Vector(0.00,0.00,10.00),App.Rotation(App.Vector(0.00,0.00,1.00),0.00))

FreeCAD.getDocument('Unnamed').getObject('Cylinder').Placement = App.Placement(App.Vector(0.00,0.00,11.00),App.Rotation(App.Vector(0.00,0.00,1.00),0.00))

FreeCAD.getDocument('Unnamed').getObject('Cylinder').Placement = App.Placement(App.Vector(0.00,0.00,13.00),App.Rotation(App.Vector(0.00,0.00,1.00),0.00))

FreeCAD.getDocument('Unnamed').getObject('Cylinder').Placement = App.Placement(App.Vector(0.00,0.00,14.00),App.Rotation(App.Vector(0.00,0.00,1.00),0.00))

FreeCAD.getDocument('Unnamed').getObject('Cylinder').Placement = App.Placement(App.Vector(0.00,0.00,15.00),App.Rotation(App.Vector(0.00,0.00,1.00),0.00))

FreeCAD.getDocument('Unnamed').getObject('Cylinder').Placement = App.Placement(App.Vector(0.00,0.00,17.00),App.Rotation(App.Vector(0.00,0.00,1.00),0.00))

FreeCAD.getDocument('Unnamed').getObject('Cylinder').Placement = App.Placement(App.Vector(0.00,0.00,18.00),App.Rotation(App.Vector(0.00,0.00,1.00),0.00))

FreeCAD.getDocument('Unnamed').getObject('Cylinder').Placement = App.Placement(App.Vector(0.00,0.00,20.00),App.Rotation(App.Vector(0.00,0.00,1.00),0.00))

FreeCAD.getDocument('Unnamed').getObject('Cylinder').Placement = App.Placement(App.Vector(0.00,0.00,21.00),App.Rotation(App.Vector(0.00,0.00,1.00),0.00))

FreeCAD.getDocument('Unnamed').getObject('Cylinder').Placement = App.Placement(App.Vector(0.00,0.00,22.00),App.Rotation(App.Vector(0.00,0.00,1.00),0.00))

FreeCAD.getDocument('Unnamed').getObject('Cylinder').Placement = App.Placement(App.Vector(0.00,0.00,23.00),App.Rotation(App.Vector(0.00,0.00,1.00),0.00))

FreeCAD.getDocument('Unnamed').getObject('Cylinder').Placement = App.Placement(App.Vector(0.00,0.00,24.00),App.Rotation(App.Vector(0.00,0.00,1.00),0.00))

FreeCAD.getDocument('Unnamed').getObject('Cylinder').Placement = App.Placement(App.Vector(0.00,0.00,26.00),App.Rotation(App.Vector(0.00,0.00,1.00),0.00))

FreeCAD.getDocument('Unnamed').getObject('Cylinder').Placement = App.Placement(App.Vector(0.00,0.00,27.00),App.Rotation(App.Vector(0.00,0.00,1.00),0.00))

FreeCAD.getDocument('Unnamed').getObject('Cylinder').Placement = App.Placement(App.Vector(0.00,0.00,28.00),App.Rotation(App.Vector(0.00,0.00,1.00),0.00))

FreeCAD.getDocument('Unnamed').getObject('Cylinder').Placement = App.Placement(App.Vector(0.00,0.00,29.00),App.Rotation(App.Vector(0.00,0.00,1.00),0.00))

FreeCAD.getDocument('Unnamed').getObject('Cylinder').Placement = App.Placement(App.Vector(0.00,0.00,30.00),App.Rotation(App.Vector(0.00,0.00,1.00),0.00))

FreeCAD.getDocument('Unnamed').getObject('Cylinder').Placement = App.Placement(App.Vector(0.00,0.00,32.00),App.Rotation(App.Vector(0.00,0.00,1.00),0.00))

FreeCAD.getDocument('Unnamed').getObject('Cylinder').Placement = App.Placement(App.Vector(0.00,0.00,33.00),App.Rotation(App.Vector(0.00,0.00,1.00),0.00))

FreeCAD.getDocument('Unnamed').getObject('Cylinder').Placement = App.Placement(App.Vector(0.00,0.00,34.00),App.Rotation(App.Vector(0.00,0.00,1.00),0.00))

FreeCAD.getDocument('Unnamed').getObject('Cylinder').Placement = App.Placement(App.Vector(0.00,0.00,35.00),App.Rotation(App.Vector(0.00,0.00,1.00),0.00))

FreeCAD.getDocument('Unnamed').getObject('Cylinder').Placement = App.Placement(App.Vector(0.00,0.00,36.00),App.Rotation(App.Vector(0.00,0.00,1.00),0.00))

FreeCAD.getDocument('Unnamed').getObject('Cylinder').Placement = App.Placement(App.Vector(0.00,0.00,38.00),App.Rotation(App.Vector(0.00,0.00,1.00),0.00))

FreeCAD.getDocument('Unnamed').getObject('Cylinder').Placement = App.Placement(App.Vector(0.00,0.00,39.00),App.Rotation(App.Vector(0.00,0.00,1.00),0.00))

FreeCAD.getDocument('Unnamed').getObject('Cylinder').Placement = App.Placement(App.Vector(0.00,0.00,40.00),App.Rotation(App.Vector(0.00,0.00,1.00),0.00))

FreeCAD.getDocument('Unnamed').getObject('Cylinder').Placement = App.Placement(App.Vector(0.00,-1.00,40.00),App.Rotation(App.Vector(0.00,0.00,1.00),0.00))

FreeCAD.getDocument('Unnamed').getObject('Cylinder').Placement = App.Placement(App.Vector(0.00,-2.00,40.00),App.Rotation(App.Vector(0.00,0.00,1.00),0.00))

FreeCAD.getDocument('Unnamed').getObject('Cylinder').Placement = App.Placement(App.Vector(0.00,-3.00,40.00),App.Rotation(App.Vector(0.00,0.00,1.00),0.00))

FreeCAD.getDocument('Unnamed').getObject('Cylinder').Placement = App.Placement(App.Vector(0.00,-2.00,40.00),App.Rotation(App.Vector(0.00,0.00,1.00),0.00))

FreeCAD.getDocument('Unnamed').getObject('Cylinder').Placement = App.Placement(App.Vector(0.00,-1.00,40.00),App.Rotation(App.Vector(0.00,0.00,1.00),0.00))

FreeCAD.getDocument('Unnamed').getObject('Cylinder').Placement = App.Placement(App.Vector(0.00,0.00,40.00),App.Rotation(App.Vector(0.00,0.00,1.00),0.00))

FreeCAD.getDocument('Unnamed').getObject('Cylinder').Placement = App.Placement(App.Vector(0.00,1.00,40.00),App.Rotation(App.Vector(0.00,0.00,1.00),0.00))

FreeCAD.getDocument('Unnamed').getObject('Cylinder').Placement = App.Placement(App.Vector(0.00,2.00,40.00),App.Rotation(App.Vector(0.00,0.00,1.00),0.00))

FreeCAD.getDocument('Unnamed').getObject('Cylinder').Placement = App.Placement(App.Vector(0.00,3.00,40.00),App.Rotation(App.Vector(0.00,0.00,1.00),0.00))

FreeCAD.getDocument('Unnamed').getObject('Cylinder').Placement = App.Placement(App.Vector(0.00,4.00,40.00),App.Rotation(App.Vector(0.00,0.00,1.00),0.00))

FreeCAD.getDocument('Unnamed').getObject('Cylinder').Placement = App.Placement(App.Vector(0.00,5.00,40.00),App.Rotation(App.Vector(0.00,0.00,1.00),0.00))

FreeCAD.getDocument('Unnamed').getObject('Cylinder').Placement = App.Placement(App.Vector(0.00,6.00,40.00),App.Rotation(App.Vector(0.00,0.00,1.00),0.00))

FreeCAD.getDocument('Unnamed').getObject('Cylinder').Placement = App.Placement(App.Vector(0.00,7.00,40.00),App.Rotation(App.Vector(0.00,0.00,1.00),0.00))

FreeCAD.getDocument('Unnamed').getObject('Cylinder').Placement = App.Placement(App.Vector(0.00,8.00,40.00),App.Rotation(App.Vector(0.00,0.00,1.00),0.00))

FreeCAD.getDocument('Unnamed').getObject('Cylinder').Placement = App.Placement(App.Vector(0.00,9.00,40.00),App.Rotation(App.Vector(0.00,0.00,1.00),0.00))

FreeCAD.getDocument('Unnamed').getObject('Cylinder').Placement = App.Placement(App.Vector(-1.00,9.00,40.00),App.Rotation(App.Vector(0.00,0.00,1.00),0.00))

FreeCAD.getDocument('Unnamed').getObject('Cylinder').Placement = App.Placement(App.Vector(-2.00,9.00,40.00),App.Rotation(App.Vector(0.00,0.00,1.00),0.00))

FreeCAD.getDocument('Unnamed').getObject('Cylinder').Placement = App.Placement(App.Vector(-3.00,9.00,40.00),App.Rotation(App.Vector(0.00,0.00,1.00),0.00))

FreeCAD.getDocument('Unnamed').getObject('Cylinder').Placement = App.Placement(App.Vector(-4.00,9.00,40.00),App.Rotation(App.Vector(0.00,0.00,1.00),0.00))

FreeCAD.getDocument('Unnamed').getObject('Cylinder').Placement = App.Placement(App.Vector(-3.00,9.00,40.00),App.Rotation(App.Vector(0.00,0.00,1.00),0.00))

FreeCAD.getDocument('Unnamed').getObject('Cylinder').Placement = App.Placement(App.Vector(-2.00,9.00,40.00),App.Rotation(App.Vector(0.00,0.00,1.00),0.00))

FreeCAD.getDocument('Unnamed').getObject('Cylinder').Placement = App.Placement(App.Vector(-1.00,9.00,40.00),App.Rotation(App.Vector(0.00,0.00,1.00),0.00))

FreeCAD.getDocument('Unnamed').getObject('Cylinder').Placement = App.Placement(App.Vector(0.00,9.00,40.00),App.Rotation(App.Vector(0.00,0.00,1.00),0.00))

FreeCAD.getDocument('Unnamed').getObject('Cylinder').Placement = App.Placement(App.Vector(1.00,9.00,40.00),App.Rotation(App.Vector(0.00,0.00,1.00),0.00))

FreeCAD.getDocument('Unnamed').getObject('Cylinder').Placement = App.Placement(App.Vector(2.00,9.00,40.00),App.Rotation(App.Vector(0.00,0.00,1.00),0.00))

FreeCAD.getDocument('Unnamed').getObject('Cylinder').Placement = App.Placement(App.Vector(3.00,9.00,40.00),App.Rotation(App.Vector(0.00,0.00,1.00),0.00))

FreeCAD.getDocument('Unnamed').getObject('Cylinder').Placement = App.Placement(App.Vector(4.00,9.00,40.00),App.Rotation(App.Vector(0.00,0.00,1.00),0.00))

FreeCAD.getDocument('Unnamed').getObject('Cylinder').Placement = App.Placement(App.Vector(5.00,9.00,40.00),App.Rotation(App.Vector(0.00,0.00,1.00),0.00))

FreeCAD.getDocument('Unnamed').getObject('Cylinder').Placement = App.Placement(App.Vector(6.00,9.00,40.00),App.Rotation(App.Vector(0.00,0.00,1.00),0.00))

FreeCAD.getDocument('Unnamed').getObject('Cylinder').Placement = App.Placement(App.Vector(7.00,9.00,40.00),App.Rotation(App.Vector(0.00,0.00,1.00),0.00))

FreeCAD.getDocument('Unnamed').getObject('Cylinder').Placement = App.Placement(App.Vector(8.00,9.00,40.00),App.Rotation(App.Vector(0.00,0.00,1.00),0.00))

FreeCAD.getDocument('Unnamed').getObject('Cylinder').Placement = App.Placement(App.Vector(9.00,9.00,40.00),App.Rotation(App.Vector(0.00,0.00,1.00),0.00))

# Gui.Selection.clearSelection()
# Gui.Selection.addSelection('Unnamed','Cylinder')
FreeCADGui.getDocument('Unnamed').getObject('Cylinder').ShapeColor = (1.00,0.00,0.00)

# Gui.Selection.clearSelection()
# Gui.Selection.addSelection('Unnamed','Box')
# Gui.Selection.addSelection('Unnamed','Cylinder')
### Begin command Part_Cut
App.activeDocument().addObject("Part::Cut","Cut")
App.activeDocument().Cut.Base = App.activeDocument().Box
App.activeDocument().Cut.Tool = App.activeDocument().Cylinder
# Gui.activeDocument().Box.Visibility=False
# Gui.activeDocument().Cylinder.Visibility=False
# App.getDocument('Unnamed').getObject('Cut').ViewObject.ShapeColor=getattr(App.getDocument('Unnamed').getObject('Box').getLinkedObject(True).ViewObject,'ShapeColor',App.getDocument('Unnamed').getObject('Cut').ViewObject.ShapeColor)
# App.getDocument('Unnamed').getObject('Cut').ViewObject.DisplayMode=getattr(App.getDocument('Unnamed').getObject('Box').getLinkedObject(True).ViewObject,'DisplayMode',App.getDocument('Unnamed').getObject('Cut').ViewObject.DisplayMode)
App.ActiveDocument.recompute()
### End command Part_Cut
# Gui.Selection.clearSelection()
# Macro End: /home/henrique/snap/freecad/common/criarBloco.FCMacro +++++++++++++++++++++++++++++++++++++++++++++++++
