# -*- coding: utf-8 -*-

# Macro Begin: /home/henrique/snap/freecad/common/part.FCMacro +++++++++++++++++++++++++++++++++++++++++++++++++
import FreeCAD
import Part
import PartDesignGui

print(" ")
print("----------")

Gui.activateWorkbench("PartWorkbench")
planilhaProgramaCNC = App.activeDocument().getObject('Programa_CNC')

def lerTamanhoBloco():
    planilhaProgramaCNC = App.activeDocument().getObject('Programa_CNC')
    P101_Lado_1_Z = planilhaProgramaCNC.get('Z_P101')
    P102_Lado_1_X = planilhaProgramaCNC.get('X_P102')
    P103_Lado_1_Y = planilhaProgramaCNC.get('Y_P103')
    #print(" ")
    #print("Lendo tamanho do bloco")
    #print('P101 = '+str(P101_Lado_1_Z))
    #print('P102 = '+str(P102_Lado_1_X))
    #print('P103 = '+str(P103_Lado_1_Y))
    return P101_Lado_1_Z, P102_Lado_1_X, P103_Lado_1_Y

def modelarBloco(P101_Lado_1_Z, P102_Lado_1_X, P103_Lado_1_Y):
    App.activeDocument().Label = "Bloco hidráulico"
    objectName = "Bloco_Faceado"
    App.ActiveDocument.addObject("Part::Box",objectName)
    App.ActiveDocument.getObject(objectName).Label = "Bloco Maciço"
    App.ActiveDocument.getObject(objectName).Length = P102_Lado_1_X
    App.ActiveDocument.getObject(objectName).Width = P103_Lado_1_Y
    App.ActiveDocument.getObject(objectName).Height = P101_Lado_1_Z
    App.ActiveDocument.getObject(objectName).Placement = App.Placement(App.Vector(0.00,-P103_Lado_1_Y,0.00),App.Rotation(App.Vector(0.00,0.00,1.00),0.00))
    FreeCADGui.ActiveDocument.getObject(objectName).Transparency = 70
    App.ActiveDocument.recompute()

def modelarFuro(numFuro, lado, diam, X, Y, Zi, Zf, sub, L, P101_Lado_1_Z, P102_Lado_1_X, P103_Lado_1_Y):
    alturaPontaBroca = float(diam) * 0.3004
    objectName = "Furo" + str(numFuro)
    App.ActiveDocument.addObject("Part::Cylinder",objectName)
    App.ActiveDocument.ActiveObject.Label = str(numFuro) + " - Furo Ø" + str(diam) + " - " + str(sub)
    App.ActiveDocument.getObject(objectName).Radius = diam/2
    App.ActiveDocument.getObject(objectName).Height = Zi - Zf - alturaPontaBroca
    coneName = "Cone" + str(numFuro)
    App.ActiveDocument.addObject("Part::Cone",coneName)
    App.ActiveDocument.getObject(coneName).Height = alturaPontaBroca
    if lado == 1:
        X_Furo = X
        Y_Furo = -Y-P103_Lado_1_Y
        Z_Furo = -Zi
        App.ActiveDocument.getObject(objectName).Placement = App.Placement(App.Vector(X_Furo,Y_Furo,Z_Furo),App.Rotation(App.Vector(0.00,0.00,1.00),0.00))
        Z_Furo = -Zf - alturaPontaBroca
        App.ActiveDocument.getObject(coneName).Placement = App.Placement(App.Vector(X_Furo,Y_Furo,Z_Furo),App.Rotation(App.Vector(0.00,0.00,1.00),0.00))
        App.ActiveDocument.getObject(coneName).Radius1 = diam/2
        App.ActiveDocument.getObject(coneName).Radius2 = '0.00 mm'
    elif lado == 2:
        X_Furo = X
        Y_Furo = -Zf-P103_Lado_1_Y-alturaPontaBroca
        Z_Furo = float(P101_Lado_1_Z) + float(Y)
        App.ActiveDocument.getObject(objectName).Placement = App.Placement(App.Vector(X_Furo,Y_Furo,Z_Furo),App.Rotation(App.Vector(1.00,0.00,0.00),90.00))
        Y_Furo = -Zf-P103_Lado_1_Y
        App.ActiveDocument.getObject(coneName).Placement = App.Placement(App.Vector(X_Furo,Y_Furo,Z_Furo),App.Rotation(App.Vector(1.00,0.00,0.00),90.00))
        App.ActiveDocument.getObject(coneName).Radius1 = '0.00 mm'
        App.ActiveDocument.getObject(coneName).Radius2 = diam/2
    elif lado == 3:
        X_Furo = X
        Y_Furo = Y
        Z_Furo = P101_Lado_1_Z + Zf + alturaPontaBroca
        App.ActiveDocument.getObject(objectName).Placement = App.Placement(App.Vector(X_Furo,Y_Furo,Z_Furo),App.Rotation(App.Vector(0.00,0.00,1.00),0.00))
        Z_Furo = P101_Lado_1_Z + Zf
        App.ActiveDocument.getObject(coneName).Placement = App.Placement(App.Vector(X_Furo,Y_Furo,Z_Furo),App.Rotation(App.Vector(0.00,0.00,1.00),0.00))
        App.ActiveDocument.getObject(coneName).Radius1 = '0.00 mm'
        App.ActiveDocument.getObject(coneName).Radius2 = diam/2
    elif lado == 4:
        X_Furo = X
        Y_Furo = Zi
        Z_Furo = -Y
        App.ActiveDocument.getObject(objectName).Placement = App.Placement(App.Vector(X_Furo,Y_Furo,Z_Furo),App.Rotation(App.Vector(1.00,0.00,0.00),90.00))
        Y_Furo = Zf + alturaPontaBroca
        App.ActiveDocument.getObject(coneName).Placement = App.Placement(App.Vector(X_Furo,Y_Furo,Z_Furo),App.Rotation(App.Vector(1.00,0.00,0.00),90.00))
        App.ActiveDocument.getObject(coneName).Radius1 = diam/2
        App.ActiveDocument.getObject(coneName).Radius2 = '0.00 mm'
    elif lado == 5:
        X_Furo = -Zi
        Y_Furo = -P103_Lado_1_Y + X
        Z_Furo = -Y
        App.ActiveDocument.getObject(objectName).Placement = App.Placement(App.Vector(X_Furo,Y_Furo,Z_Furo),App.Rotation(App.Vector(0.00,1.00,0.00),90.00))
        X_Furo = -Zf - alturaPontaBroca
        App.ActiveDocument.getObject(coneName).Placement = App.Placement(App.Vector(X_Furo,Y_Furo,Z_Furo),App.Rotation(App.Vector(0.00,1.00,0.00),90.00))
        App.ActiveDocument.getObject(coneName).Radius1 = diam/2
        App.ActiveDocument.getObject(coneName).Radius2 = '0.00 mm'
    elif lado == 6:
        X_Furo = P102_Lado_1_X + Zf + alturaPontaBroca
        Y_Furo = -P103_Lado_1_Y + X
        Z_Furo = P101_Lado_1_Z + Y
        App.ActiveDocument.getObject(objectName).Placement = App.Placement(App.Vector(X_Furo,Y_Furo,Z_Furo),App.Rotation(App.Vector(0.00,1.00,0.00),90.00))
        X_Furo = P102_Lado_1_X + Zf
        App.ActiveDocument.getObject(coneName).Placement = App.Placement(App.Vector(X_Furo,Y_Furo,Z_Furo),App.Rotation(App.Vector(0.00,1.00,0.00),90.00))
        App.ActiveDocument.getObject(coneName).Radius1 = '0.00 mm'
        App.ActiveDocument.getObject(coneName).Radius2 = diam/2
    if L=="P":
        FreeCADGui.ActiveDocument.getObject(objectName).ShapeColor = (1.00,0.00,0.00)
        FreeCADGui.ActiveDocument.getObject(coneName).ShapeColor = (1.00,0.00,0.00)
    elif L=="T":
        FreeCADGui.ActiveDocument.getObject(objectName).ShapeColor = (0.00,1.00,0.00)
        FreeCADGui.ActiveDocument.getObject(coneName).ShapeColor = (0.00,1.00,0.00)
    elif L=="A":
        FreeCADGui.ActiveDocument.getObject(objectName).ShapeColor = (1.00,1.00,0.00)
        FreeCADGui.ActiveDocument.getObject(coneName).ShapeColor = (1.00,1.00,0.00)
    elif L=="B":
        FreeCADGui.ActiveDocument.getObject(objectName).ShapeColor = (0.00,0.00,1.00)
        FreeCADGui.ActiveDocument.getObject(coneName).ShapeColor = (0.00,0.00,1.00)
    elif L=="FuroCentro":
        FreeCADGui.ActiveDocument.getObject(objectName).ShapeColor = (0.00,0.00,0.00)
        FreeCADGui.ActiveDocument.getObject(coneName).ShapeColor = (0.00,0.00,0.00)
    App.ActiveDocument.recompute()

def lerLinha(x):
    Lado = planilhaProgramaCNC.get('B'+str(x))
    if x>3:
        ladoAnterior = planilhaProgramaCNC.get('B'+str(x-1))
    else:
        ladoAnterior = Lado
    T = planilhaProgramaCNC.get('D'+str(x))
    descFerr = planilhaProgramaCNC.get('E'+str(x))
    diam = planilhaProgramaCNC.get('F'+str(x))
    S = planilhaProgramaCNC.get('H'+str(x))
    F = planilhaProgramaCNC.get('J'+str(x))
    X = planilhaProgramaCNC.get('L'+str(x))
    Y = planilhaProgramaCNC.get('N'+str(x))
    Zi = planilhaProgramaCNC.get('P'+str(x))
    Zf = planilhaProgramaCNC.get('R'+str(x))
    sub = planilhaProgramaCNC.get('S'+str(x))
    L = planilhaProgramaCNC.get('T'+str(x))
    varX = planilhaProgramaCNC.get('U'+str(x))
    varY = planilhaProgramaCNC.get('V'+str(x))
    #print(" ")
    #print("Lendo linha " + str(x))
    ##print('Lado = '+str(Lado))
    ##print('T = '+str(T))
    ##print('descFerr = '+str(descFerr))
    ##print('diam = '+str(diam))
    ##print('S = '+str(S))
    ##print('F = '+str(F))
    #print('X = '+str(X))
    ##print('Y = '+str(Y))
    ##print('Zi = '+str(Zi))
    ##print('Zf = '+str(Zf))
    ##print('sub = '+str(sub))
    ##print('L = '+str(L))
    return Lado, T, descFerr, diam, S, F, X, Y, Zi, Zf, sub, L, varX, varY, ladoAnterior

#Iniciar programa
P101_Lado_1_Z, P102_Lado_1_X, P103_Lado_1_Y = lerTamanhoBloco()
modelarBloco(P101_Lado_1_Z, P102_Lado_1_X, P103_Lado_1_Y)
linhaAtual = 3
Lado, T, descFerr, diam, S, F, X, Y, Zi, Zf, sub, L, varX, varY, ladoAnterior = lerLinha(3)
nomePrograma = App.activeDocument().getObject('Programa_CNC').get('nomePrograma')

while sub != "FIM DO BLOCO HIDRÁULICO":
    Lado, T, descFerr, diam, S, F, X, Y, Zi, Zf, sub, L, varX, varY, ladoAnterior = lerLinha(linhaAtual)  
    #print(sub)
    if sub == "INICIO DO BLOCO HIDRÁULICO":
        prg = "%" + nomePrograma + ",MX--,"
        prg +=  ";" + '\n'
        prg +=  ";EMPRESA.......> HL HIDRAUMAK" + '\n'
        prg +=  ";MAQUINA.......> TRAVIS_M1000 - FAGOR" + '\n'
        prg +=  ";PROGRAMADOR...> HENRIQUE" + '\n'
        prg +=  ";PECA..........> BLOCO " + nomePrograma + '\n'
        prg +=  ";" + '\n'
        prg +=  ';***FERRAMENTAS***' + '\n'
        prg += '(P101 = ' + str(P101_Lado_1_Z) + '); EIXO Z LADO 1' + '\n'
        prg += "(P102 = " + str(P102_Lado_1_X) + "); EIXO X LADO 1" + '\n'
        prg +=  "(P103 = " + str(P103_Lado_1_Y) +  "); EIXO Y LADO 1" + '\n'
        prg +=  '(MSG "DEIXE O LADO ' + str(Lado) + ' PARA CIMA"")' + '\n'
        prg +=  "M0" + '\n'
        prg +=  ";" + '\n'
        prg +=  ";AJUSTAR ALTURA DA FACE" + '\n'
        if Lado == 1:
            prg += "(P100 = P101); AJUSTE DA ALTURA"
        if Lado == 2:
            prg += "(P100 = P103); AJUSTE DA ALTURA"
        if Lado == 3:
            prg += "(P100 = P101); AJUSTE DA ALTURA"
        if Lado == 4:
            prg += "(P100 = P103); AJUSTE DA ALTURA"
        if Lado == 5:
            prg += "(P100 = P102); AJUSTE DA ALTURA"
        if Lado == 6:
            prg += "(P100 = P102); AJUSTE DA ALTURA"
        prg += '\n' + "(MCALL 2)" + '\n'
        prg +=  "(MDOFF )" + '\n'
        prg +=  ";*** INICIO DO LADO " + str(Lado) + " ***" + '\n'
        prg +=  "G53 G00 Z-10." + '\n'
        prg +=  ";" + '\n'
        prg +=  "G54" + '\n'
        prg +=  "G71 G40 G80" + '\n'
        prg +=  "T" + str(T) + "D" + str(T) + "; " + str(descFerr) + ' ' + str(diam) + '\n'
        prg +=  '(MSG "L' + str(Lado) + " - DIAM " + str(diam) + ' - ' + str(descFerr) + '")' + '\n'
        prg +=  "M06" + '\n'
        prg +=  "G54" + '\n'
        prg +=  "G90 G94" + '\n'
        prg +=  "G07" + '\n'
        prg +=  "S" + str(S) + " M03" + '\n'
    elif sub == "TROCA DE FERRAMENTA":
        prg +=  ";Troca de ferramenta" + '\n'
        prg +=  "M09; Desligar refrigeracao" + '\n'
        prg +=  "G53 G00 Z-10.; Subir a ferramenta" + '\n'
        prg +=  "T" + str(T) + "D" + str(T) + "; " + str(descFerr) + ' ' + str(diam) + '\n'
        prg +=  '(MSG "L' + str(Lado) + " - DIAM " + str(diam) + ' - ' + str(descFerr) + '")' + '\n'
        prg +=  "M06" + '\n'
        prg +=  "G54" + '\n'
        prg +=  "G90 G94" + '\n'
        prg +=  "G07" + '\n'
        prg +=  "S" + str(S) + " M03" + '\n'
    elif sub == "APROXIMAR DO FURO":
        prg +=  "(P1=" + str(varX) + ")" + '\n'
        prg +=  "(P2=" + str(varY) + ")" + '\n'
        prg +=  "G00 XP1 YP2" + '\n'
        prg +=  "    Z" + str(Zi) + '\n'
        prg +=  "    Z" + str(Zf) + '\n'
    elif sub == "LIGAR REFRIGERAÇÃO":
        prg +=  "M08; Ligar refrigeracao" + '\n'
    elif sub == "SAIR DO FURO":
        prg +=  "    Z" + str(Zf) + '\n'
    elif sub == "DESLIGAR REFRIGERAÇÃO":
        prg +=  "M09; Desligar refrigeracao" + '\n'
    elif sub == "TROCAR LADO BLOCO HIDRAULICO":
        prg +=  "G05" + '\n'
        prg +=  "M05; Parar ferramenta" + '\n'
        prg +=  ";*** FIM DO LADO " + str(ladoAnterior) + ' ***\n'
        prg +=  "G53 G00 Z-10.; Subir a ferramenta" + '\n'
        prg +=  "G53 G00 Y-10.; Trazer a mesa para frente"+ '\n'
        prg +=  '(MSG "DEIXE O LADO ' + str(Lado) + ' PARA CIMA"")' + '\n'
        prg +=  "M0" + '\n'
        if Lado == 1:
            prg += "(P100 = P101); AJUSTE DA ALTURA"
        if Lado == 2:
            prg += "(P100 = P103); AJUSTE DA ALTURA"
        if Lado == 3:
            prg += "(P100 = P101); AJUSTE DA ALTURA"
        if Lado == 4:
            prg += "(P100 = P103); AJUSTE DA ALTURA"
        if Lado == 5:
            prg += "(P100 = P102); AJUSTE DA ALTURA"
        if Lado == 6:
            prg += "(P100 = P102); AJUSTE DA ALTURA"
        prg += '\n' + "(MCALL 2)" + '\n'
        prg +=  "(MDOFF )" + '\n'
        prg +=  ";*** INICIO DO LADO " + str(Lado) + " ***" + '\n'
        prg +=  "G71 G40 G80" + '\n'
        prg +=  "T" + str(T) + "D" + str(T) + "; " + str(descFerr) + ' ' + str(diam) + '\n'
        prg +=  '(MSG "L' + str(Lado) + " - DIAM " + str(diam) + ' - ' + str(descFerr) + '")' + '\n'
        prg +=  "M06" + '\n'
        prg +=  "G54" + '\n'
        prg +=  "G90 G94" + '\n'
        prg +=  "G07" + '\n'
        prg +=  "S" + str(S) + " M03" + '\n'
    elif sub == "PICA-PAU SEM RETORNO":
        prg +=  ";Pica-pau sem retorno" + '\n'
        prg +=  "(P104=" + str(Zi) + "); Profundidade inicial" + '\n'
        prg +=  "(P105=" + str(Zf) + "); Profundidade final" + '\n'
        prg +=  "(P106=" + str(F) + "); Avanco" + '\n'
        prg +=  "(P107=2); Profundidade inicial" + '\n'
        prg +=  "(MCALL 3); PICA-PAU SEM RETORNO" + '\n'
        prg +=  "(MDOFF)" + '\n'
        prg +=  ";" + '\n'
        modelarFuro(linhaAtual, Lado, diam, X, Y, Zi, Zf, sub, L, P101_Lado_1_Z, P102_Lado_1_X, P103_Lado_1_Y)
    elif sub == "PICA-PAU COM RETORNO A Z2":
        prg +=  ";Pica-pau com retorno a Z2" + '\n'
        prg +=  "(P104=" + str(Zi) + "); Profundidade inicial" + '\n'
        prg +=  "(P105=" + str(Zf) + "); Profundidade final" + '\n'
        prg +=  "(P106=" + str(F) + "); Avanco" + '\n'
        prg +=  "(P107=2); Profundidade inicial" + '\n'
        prg +=  "(MCALL 4); PICA-PAU COM RETORNO A Z2" + '\n'
        prg +=  "(MDOFF)" + '\n'
        prg +=  ";" + '\n'
        modelarFuro(linhaAtual, Lado, diam, X, Y, Zi, Zf, sub, L, P101_Lado_1_Z, P102_Lado_1_X, P103_Lado_1_Y)
    elif sub == "FURO DE CENTRO":
        modelarFuro(linhaAtual, Lado, diam, X, Y, Zi, Zf, sub, "FuroCentro", P101_Lado_1_Z, P102_Lado_1_X, P103_Lado_1_Y)
    linhaAtual += 1

'''
App.activeDocument().addObject("Part::Cut","Bloco_Hidraulico")
App.activeDocument().Bloco_Hidraulico.Base = App.activeDocument().Bloco_Faceado
App.activeDocument().Bloco_Hidraulico.Tool = App.activeDocument().Furo
FreeCADGui.ActiveDocument.ActiveObject.Transparency = 90'''
arquivo = "/home/henrique/Downloads/001000.pim"
escrever = open(arquivo, "w")
escrever.write(prg)
escrever.close()
App.ActiveDocument.recompute()
Gui.SendMsgToActiveView("ViewFit")

#App.ActiveDocument.getObject('Programa_CNC').ViewObject.doubleClicked()
